XDLMS_1 {joint_iso_itu_t association_control(2) modules(0) apdus(0) version1(1)}
--  XDLMS_1 refers to xDLMS version 1
DEFINITIONS ::=
BEGIN

--  The data types Name and RelativeDistinguishedName are imported from ISO/IEC 9594_2.
--  object identifier assignments
acse_as_id OBJECT IDENTIFIER ::=
  {joint_iso_itu_t association_control(2) abstract_syntax(1) apdus(0)
   version1(1)}

--  may be used to reference the abstract syntax of the ACSE APDUs
aCSE_id OBJECT IDENTIFIER ::=
  {joint_iso_itu_t association_control(2) ase_id(3) acse_ase(1) version(1)}


------------------------------------------------------
--  may be used to identify the COSEMpdu.
--  top level CHOICE
COSEMpdu ::= CHOICE {
-- standardized DLMS PDUs used in COSEM
-- DLMS PDUs (no encryption selected 24)
  initiateRequest          [1]  IMPLICIT InitiateRequest, 
  readRequest              [5]  IMPLICIT ReadRequest,
  writeRequest             [6]  IMPLICIT WriteRequest,
  initiateResponse         [8]  IMPLICIT InitiateResponse,
  readResponse             [12] IMPLICIT ReadResponse,
  writeResponse            [13] IMPLICIT WriteResponse,
  confirmedServiceError    [14] ConfirmedServiceError,
  unconfirmedWriteRequest  [22] IMPLICIT UnconfirmedWriteRequest,
  informationReportRequest [24] IMPLICIT InformationReportRequest,

-- the four ACSE APDUs
--  aarq AARQ-apdu
--  aare AARE-apdu
--  rlrq RLRQ-apdu -- -- OPTIONAL
--  rlre RLRE-apdu -- -- OPTIONAL

-- APDUs used for data communication services using LN referencing
  get-request                [192] GET-Request,
  set-request                [193] SET-Request,
  event-notification-request [194] IMPLICIT EVENT-NOTIFICATION-Request,
  action-request             [195] ACTION-Request,
  get-response               [196] GET-Response,
  set-response               [197] SET-Response,
  action-response            [199] ACTION-Response,

-- global ciphered pdus
  glo-get-request                [200] IMPLICIT OCTET STRING,
  glo-set-request                [201] IMPLICIT OCTET STRING,
  glo-event-notification-request [202] IMPLICIT OCTET STRING,
  glo-action-request             [203] IMPLICIT OCTET STRING,
  glo-get-response               [204] IMPLICIT OCTET STRING,
  glo-set-response               [205] IMPLICIT OCTET STRING,
  glo-action-response            [207] IMPLICIT OCTET STRING,

-- dedicated ciphered pdus
  ded-get-request                [208] IMPLICIT OCTET STRING,
  ded-set-request                [209] IMPLICIT OCTET STRING,
  ded-event-notification-request [210] IMPLICIT OCTET STRING,
  ded-actionRequest              [211] IMPLICIT OCTET STRING,
  ded-get-response               [212] IMPLICIT OCTET STRING,
  ded-set-response               [213] IMPLICIT OCTET STRING,
  ded-action-response            [215] IMPLICIT OCTET STRING,

-- the exception response pdu 
  exception-response             [216] IMPLICIT EXCEPTION-Response
}


-------------------------------------------
-- Useful Types
Integer8   ::= INTEGER(-128..127)
Integer16  ::= INTEGER(-32768..32767)
Integer32  ::= INTEGER(-2147483648..2147483647)
Integer64  ::= INTEGER(-9223372036854775808..9223372036854775807)
Unsigned8  ::= INTEGER(0..255)
Unsigned16 ::= INTEGER(0..65535)
Unsigned32 ::= INTEGER(0..4294967295)
Unsigned64 ::= INTEGER(0..18446744073709551615)

-- A-XDR typedef for ENUMERATED
Enum ::= INTEGER(0..255)

Invoke-Id-And-Priority ::= BIT STRING (SIZE(8))
--{
--  invoke_id     (0..3),
--  reserved      (4..5),
--  service_class (6),     0 = Unconfirmed, 1 = Confirmed
--  priority      (7)      0 = normal; 1 = high
--}

-- NOTE
-- In the 3-layer, connection-oriented, HDLC based profile bit 6 is not relevant, as the service_class information is
-- conveyed by the HDLC frame type carrying the APDU.

ObjectName                 ::= Integer16
Cosem-Class-Id             ::= Unsigned16
Cosem-Object-Instance-Id   ::= OCTET STRING (SIZE(6)) -- completely written out OBIS code without seperator
Cosem-Object-Attribute-Id  ::= Integer8
Cosem-Object-Method-Id     ::= Integer8
Cosem-Date-Time            ::= OCTET STRING (SIZE(12)) -- encoded as date_time, as specified in IEC 62056-62.

Cosem-Attribute-Descriptor ::= SEQUENCE
{
  class-id     Cosem-Class-Id,
  instance-id  Cosem-Object-Instance-Id,
  attribute-id Cosem-Object-Attribute-Id
}

Cosem-Method-Descriptor ::= SEQUENCE
{
  class-id    Cosem-Class-Id,
  instance-id Cosem-Object-Instance-Id,
  method-id   Cosem-Object-Method-Id
}

Selective-Access-Descriptor ::= SEQUENCE
{
  access-selector   Unsigned8,
  access-parameters Data
}

Cosem-Attribute-Descriptor-With-Selection ::= SEQUENCE
{
  cosem-attribute-descriptor Cosem-Attribute-Descriptor,
  access-selection           Selective-Access-Descriptor OPTIONAL
}

Get-Data-Result ::= CHOICE
{
  data               [0] Data,
  data-access-result [1] IMPLICIT Data-Access-Result
}

Action-Response-With-Optional-Data ::= SEQUENCE
{
  result            Action-Result,
  return-parameters Get-Data-Result OPTIONAL
}

ConfirmedServiceError ::= CHOICE
{
  -- tag 0 is reserved
  initiateError        [1]  ServiceError, -- not applicable within DLMS context
  getStatus            [2]  ServiceError, -- not applicable within DLMS context
  getNameList          [3]  ServiceError, -- not applicable within DLMS context
  getVariableAttribute [4]  ServiceError, -- not applicable within DLMS context
  read                 [5]  ServiceError,
  write                [6]  ServiceError,
  getDataSetAttribute  [7]  ServiceError, -- not applicable within DLMS context
  getTIAttribute       [8]  ServiceError, -- not applicable within DLMS context
  changeScope          [9]  ServiceError, -- not applicable within DLMS context
  start                [10] ServiceError, -- not applicable within DLMS context
  stop                 [11] ServiceError, -- not applicable within DLMS context
  resume               [12] ServiceError, -- not applicable within DLMS context
  makeUsable           [13] ServiceError, -- not applicable within DLMS context
  initiateLoad         [14] ServiceError, -- not applicable within DLMS context
  loadSegment          [15] ServiceError, -- not applicable within DLMS context
  terminateLoad        [16] ServiceError, -- not applicable within DLMS context
  initiateUpLoad       [17] ServiceError, -- not applicable within DLMS context
  upLoadSegment        [18] ServiceError, -- not applicable within DLMS context
  terminateUpLoad      [19] ServiceError  -- not applicable within DLMS context
}


ServiceError ::= CHOICE
{
  application-reference [0] IMPLICIT ENUMERATED {
  -- DLMS provider only
    other                           (0),
    time-elapsed                    (1), -- time out since request sent
    application-unreachable         (2), -- peer AEi not reachable
    application-reference-invalid   (3), -- addressing trouble
    application-context-unsupported (4), -- application-context incompatibility
    provider-communication-error    (5), -- error at the local or distant equipment
    deciphering-error               (6)  -- error detected by the deciphering function
  },
  
  hardware-resource     [1] IMPLICIT ENUMERATED {
  -- VDE hardware troubles
    other                          (0),
    memory-unavailable             (1),
    processor-resource-unavailable (2),
    mass-storage-unavailable       (3),
    other-resource-unavailable     (4)
  },
  
  vde-state-error       [2] IMPLICIT ENUMERATED {
  -- Error source description
    other             (0),
    no-dlms-context   (1),
    loading-data-set  (2),
    status-nochange   (3),
    status-inoperable (4)
  },
  
  service               [3] IMPLICIT ENUMERATED {
  -- service handling troubles
    other               (0),
    pdu-size            (1), -- pdu too long
                             -- (refer to companion specification)
    service-unsupported (2)  -- as described in the conformance block
  },
  
  definition            [4] IMPLICIT ENUMERATED {
  -- object bound troubles in a service
    other                         (0),
    object-undefined              (1), -- object not defined at the VDE
    object-class-inconsistent     (2), -- class of object incompatible with asked service
    object-attribute-inconsistent (3) -- object attributes are inconsistent
  },

  access                [5] IMPLICIT ENUMERATED {
  -- object access error
    other                    (0),
    scope-of-access-violated (1), -- access denied through authorization reason
    object-access-invalid    (2), -- access incompatible with object attribute
    hardware-fault           (3), -- access fail for hardware reason
    object-unavailable       (4)  -- VDE hands object for unavailable
  },
  
  initiate              [6] IMPLICIT ENUMERATED {
  -- initiate service error
    other                      (0),
    dlms-version-too-low       (1), -- proposed DLMS version too low
    incompatible-conformance   (2), -- proposed services not sufficient
    pdu-size-too-short         (3), -- proposed pdu size too short
    refused-by-the-VDE-Handler (4)  -- VAA creation impossible or not allowed
  },
  
  load-data-set         [7] IMPLICIT ENUMERATED {
  -- data set load services error
    other                     (0),
    primitive-out-of-sequence (1), -- according to the DataSet
                                   -- loading state transitions
    not-loadable              (2), -- loadable attribute set to FALSE
    dataset-size-too-large    (3), -- evaluated Data Set size too large
    not-awaited-segment       (4), -- proposed segment not awaited
    interpretation-failure    (5), -- segment interpretation error
    storage-failure           (6), -- segment storage error
    data-set-not-ready        (7)  -- Data Set not in correct state for uploading
  },

  -- change-scope       [8] IMPLICIT reserved.
  
  task                  [9] IMPLICIT ENUMERATED {
  -- TI services error
    other             (0),
    no-remote-control (1), -- Remote Control parameter set to FALSE
    ti-stopped        (2), -- TI in stopped state
    ti-running        (3), -- TI in running state
    ti-unusable       (4) -- TI in unusable state
  }
  
  -- other              [10] IMPLICIT ENUMERATED
}

Data ::= CHOICE
{
  null-data            [0]   IMPLICIT NULL ,
  array                [1]   IMPLICIT SEQUENCE OF Data,
  structure            [2]   IMPLICIT SEQUENCE OF Data,
  bool                 [3]   IMPLICIT BOOLEAN ,
  bit-string           [4]   IMPLICIT BIT STRING ,
  double-long          [5]   IMPLICIT Integer32,
  double-long-unsigned [6]   IMPLICIT Unsigned32,
  octet-string         [9]   IMPLICIT OCTET STRING ,
  visible-string       [10]  IMPLICIT VisibleString,
  bcd                  [13]  IMPLICIT Integer8,
  integer              [15]  IMPLICIT Integer8,
  long-integer         [16]  IMPLICIT Integer16,
  unsigned             [17]  IMPLICIT Unsigned8,
  long-unsigned        [18]  IMPLICIT Unsigned16,
  compact-array        [19]  IMPLICIT SEQUENCE
  {
    contents-description [0] TypeDescription,
    array-contents       [1] IMPLICIT OCTET STRING
  },
  long64               [20]  IMPLICIT Integer64,
  long64-unsigned      [21]  IMPLICIT Unsigned64,
  enumerate            [22]  IMPLICIT Enum,
  float32              [23]  IMPLICIT OCTET STRING (SIZE(4)),
  float64              [24]  IMPLICIT OCTET STRING (SIZE(8)),
  date_time            [25]  IMPLICIT OCTET STRING (SIZE(12)),
  date                 [26]  IMPLICIT OCTET STRING (SIZE(5)),
  time                 [27]  IMPLICIT OCTET STRING (SIZE(4)),
  dont-care            [255] IMPLICIT NULL
}

TypeDescription ::= CHOICE
{
  null-data            [0]   IMPLICIT NULL ,
  array                [1]   IMPLICIT SEQUENCE {
    number-of-elements Unsigned16,
    type-description   TypeDescription
  },
  structure            [2]   IMPLICIT SEQUENCE OF TypeDescription,
  bool                 [3]   IMPLICIT NULL ,
  bit-string           [4]   IMPLICIT NULL ,
  double-long          [5]   IMPLICIT NULL ,
  double-long-unsigned [6]   IMPLICIT NULL ,
  octet-string         [9]   IMPLICIT NULL ,
  visible-string       [10]  IMPLICIT NULL ,
  bcd                  [13]  IMPLICIT NULL ,
  integer              [15]  IMPLICIT NULL ,
  long-integer         [16]  IMPLICIT NULL ,
  unsigned             [17]  IMPLICIT NULL ,
  long-unsigned        [18]  IMPLICIT NULL ,
  long64               [20]  IMPLICIT NULL ,
  long64-unsigned      [21]  IMPLICIT NULL ,
  enumerate            [22]  IMPLICIT NULL ,
  float32              [23]  IMPLICIT NULL ,
  float64              [24]  IMPLICIT NULL ,
  date_time            [25]  IMPLICIT NULL ,
  date                 [26]  IMPLICIT NULL ,
  time                 [27]  IMPLICIT NULL ,
  dont-care            [255] IMPLICIT NULL
}

DataBlock-G ::= SEQUENCE -- G == DataBlock for the GET.response service
{
  last-block   BOOLEAN,
  block-number Unsigned32,
  result       CHOICE {
    raw-data           [0] IMPLICIT OCTET STRING,
    data-access-result [1] IMPLICIT Data-Access-Result
  }
}

DataBlock-SA ::= SEQUENCE -- SA == DataBlock for the SET.request and
                          --       ACTION.request/.response services
{
  last-block   BOOLEAN,
  block-number Unsigned32,
  raw-data     OCTET STRING
}

Data-Access-Result ::= ENUMERATED
{
  success                   (0),
  hardware-fault            (1),
  temporary-failure         (2),
  read-write-denied         (3),
  object-undefined          (4),
  object-class-inconsistent (9),
  object-unavailable        (11),
  type-unmatched            (12),
  scope-of-access-violated  (13),
  data-block-unavailable    (14),
  long-get-aborted          (15),
  no-long-get-in-progress   (16),
  long-set-aborted          (17),
  no-long-set-in-progress   (18),
  other-reason              (250)
}

Action-Result ::= ENUMERATED
{
  success                    (0),
  hardware-fault             (1),
  temporary-failure          (2),
  read-write-denied          (3),
  object-undefined           (4),
  object-class-inconsistent  (9),
  object-unavailable         (11),
  type-unmatched             (12),
  scope-of-access-violated   (13),
  data-block-unavailable     (14),
  long-action-aborted        (15),
  no-long-action-in-progress (16),
  other-reason               (250)
}

-------------------------------------------
-- The xDLMS-Initiate.request/response PDUs
InitiateRequest ::= SEQUENCE
{
  dedicated-key                OCTET STRING OPTIONAL,
  -- shall not be encoded in DLMS without encryption
  response-allowed             BOOLEAN DEFAULT TRUE,
  proposed-quality-of-service  [0] IMPLICIT Integer8 OPTIONAL,
  proposed-dlms-version-number Unsigned8,
  proposed-conformance         Conformance,
  client-max-receive-pdu-size  Unsigned16
}

InitiateResponse ::= SEQUENCE
{
  negotiated-quality-of-service  [0] IMPLICIT Integer8 OPTIONAL,
  negotiated-dlms-version-number Unsigned8,
  negotiated-conformance         Conformance,
  server-max-receive-pdu-size    Unsigned16,
  vaa-name                       ObjectName
}

-- The value of the vaa-name in case of LN referencing is a dummy value 0x0007. In case of SN
-- referencing, its value is the base_name of the Association SN object, 0xFA00.

-- In COSEM, the quality-of-service parameter is not used. The server shall accept any value and
-- process the xDLMS-Initiate.request without considering the value of this parameter.

-------------------------------------------
-- The conformance block

-- In order to enable optimized COSEM server implementations, a conformance block with extended
-- functionality is added. The COSEM conformance block can be distinguished from the standard
-- conformance block by its tag “APPLICATION 31”.

Conformance ::= [APPLICATION 31] BIT STRING --(SIZE(24))
{
-- the bit is set when the corresponding service or functionality is available
  reserved0                     (0),
  reserved1                     (1),
  reserved2                     (2),
  read                          (3),
  write                         (4),
  unconfirmed-write             (5),
  reserved6                     (6),
  reserved7                     (7),
  attribute0-supported-with-SET (8),
  priority-mgmt-supported       (9),
  attribute0-supported-with-GET (10),
  block-transfer-with-get       (11),
  block-transfer-with-set       (12),
  block-transfer-with-action    (13),
  multiple-references           (14),
  information-report            (15),
  reserved16                    (16),
  reserved17                    (17),
  parameterized-access          (18),
  get                           (19),
  set                           (20),
  selective-access              (21),
  event-notification            (22),
  action                        (23)
}

-- The parameterized access (as additional variant of the VariableAccessSpecification) provides the
-- ReadRequest or the WriteRequest service with the capability to transport additional parameters.
-- Parameterized access is introduced by adding the following access method (compare Annex A of
-- IEC 61334-4-41, p. 221):

Variable-Access-Specification ::= CHOICE {
  variable-name        [2] IMPLICIT ObjectName,
  -- detailed access is not needed in DLMS/COSEM
  -- detailed-access      [3] IMPLICIT SEQUENCE{
  --  variable-name   ObjectName
  --  detailed-access OCTET STRING
  --},
  parameterized-access [4] IMPLICIT SEQUENCE{
    variable-name ObjectName,
    selector      Integer8,
    parameter     Data
  }
}

-- The meaning of the selector and of the access parameter depends on the referenced variable. It is
-- defined in the corresponding COSEM IC specification.

-------------------------------------------
-- COSEM APDUs using logical name referencing

GET-Request ::= CHOICE
{
  get-request-normal    [1] IMPLICIT Get-Request-Normal,
  get-request-next      [2] IMPLICIT Get-Request-Next,
  get-request-with-list [3] IMPLICIT Get-Request-With-List
}

Get-Request-Normal ::= SEQUENCE
{
  invoke-id-and-priority     Invoke-Id-And-Priority,
  cosem-attribute-descriptor Cosem-Attribute-Descriptor,
  access-selection           Selective-Access-Descriptor OPTIONAL
}

Get-Request-Next ::= SEQUENCE
{
  invoke-id-and-priority Invoke-Id-And-Priority,
  block-number           Unsigned32
}

Get-Request-With-List ::= SEQUENCE
{
  invoke-id-and-priority    Invoke-Id-And-Priority,
  attribute-descriptor-list SEQUENCE OF Cosem-Attribute-Descriptor-With-Selection
}

GET-Response ::= CHOICE
{
  get-response-normal         [1] IMPLICIT Get-Response-Normal,
  get-response-with-datablock [2] IMPLICIT Get-Response-With-Datablock,
  get-response-with-list      [3] IMPLICIT Get-Response-With-List
}

Get-Response-Normal ::= SEQUENCE
{
  invoke-id-and-priority Invoke-Id-And-Priority,
  result                 Get-Data-Result
}

Get-Response-With-Datablock ::= SEQUENCE
{
  invoke-id-and-priority Invoke-Id-And-Priority,
  result                 DataBlock-G
}

Get-Response-With-List ::= SEQUENCE
{
  invoke-id-and-priority Invoke-Id-And-Priority,
  result                 SEQUENCE OF Get-Data-Result
}

SET-Request ::= CHOICE
{
  set-request-normal                        [1] IMPLICIT Set-Request-Normal,
  set-request-with-first-datablock          [2] IMPLICIT Set-Request-With-First-Datablock,
  set-request-with-datablock                [3] IMPLICIT Set-Request-With-Datablock,
  set-request-with-list                     [4] IMPLICIT Set-Request-With-List,
  set-request-with-list-and-first-datablock [5] IMPLICIT Set-Request-With-List-And-First-Datablock
}

Set-Request-Normal ::= SEQUENCE
{
  invoke-id-and-priority     Invoke-Id-And-Priority,
  cosem-attribute-descriptor Cosem-Attribute-Descriptor,
  access-selection           Selective-Access-Descriptor OPTIONAL,
  value                      Data
}

Set-Request-With-First-Datablock ::= SEQUENCE
{
  invoke-id-and-priority     Invoke-Id-And-Priority,
  cosem-attribute-descriptor Cosem-Attribute-Descriptor,
  access-selection           Selective-Access-Descriptor OPTIONAL,
  datablock                  DataBlock-SA
}

Set-Request-With-Datablock ::= SEQUENCE
{ 
  invoke-id-and-priority Invoke-Id-And-Priority,
  datablock              DataBlock-SA
}
 
Set-Request-With-List ::= SEQUENCE
{ 
  invoke-id-and-priority    Invoke-Id-And-Priority,
  attribute-descriptor-list SEQUENCE OF Cosem-Attribute-Descriptor-With-Selection,
  value-list                SEQUENCE OF Data
}

Set-Request-With-List-And-First-Datablock ::= SEQUENCE
{
  invoke-id-and-priority    Invoke-Id-And-Priority,
  attribute-descriptor-list SEQUENCE OF Cosem-Attribute-Descriptor-With-Selection,
  datablock                 DataBlock-SA
}

SET-Response ::= CHOICE
{
  set-response-normal                   [1] IMPLICIT Set-Response-Normal,
  set-response-datablock                [2] IMPLICIT Set-Response-Datablock,
  set-response-last-datablock           [3] IMPLICIT Set-Response-Last-Datablock,
  set-response-last-datablock-with-list [4] IMPLICIT Set-Response-Last-Datablock-With-List,
  set-response-with-list                [5] IMPLICIT Set-Response-With-List
}

Set-Response-Normal ::= SEQUENCE
{ 
  invoke-id-and-priority Invoke-Id-And-Priority,
  result                 Data-Access-Result
} 

Set-Response-Datablock ::= SEQUENCE
{ 
  invoke-id-and-priority Invoke-Id-And-Priority,
  block-number           Unsigned32
}
 
Set-Response-Last-Datablock ::= SEQUENCE
{ 
  invoke-id-and-priority Invoke-Id-And-Priority,
  result                 Data-Access-Result,
  block-number           Unsigned32
} 

Set-Response-Last-Datablock-With-List ::= SEQUENCE
{
  invoke-id-and-priority Invoke-Id-And-Priority,
  result                 SEQUENCE OF Data-Access-Result,
  block-number           Unsigned32
}

Set-Response-With-List ::= SEQUENCE
{ 
  invoke-id-and-priority Invoke-Id-And-Priority,
  result                 SEQUENCE OF Data-Access-Result
} 

ACTION-Request ::= CHOICE
{ 
  action-request-normal                     [1] IMPLICIT Action-Request-Normal,
  action-request-next-pblock                [2] IMPLICIT Action-Request-Next-Pblock,
  action-request-with-list                  [3] IMPLICIT Action-Request-With-List,
  action-request-with-first-pblock          [4] IMPLICIT Action-Request-With-First-Pblock,
  action-request-with-list-and-first-pblock [5] IMPLICIT Action-Request-With-List-And-First-Pblock,
  action-request-with-pblock                [6] IMPLICIT Action-Request-With-Pblock
}

Action-Request-Normal ::= SEQUENCE
{
  invoke-id-and-priority       Invoke-Id-And-Priority,
  cosem-method-descriptor      Cosem-Method-Descriptor,
  method-invocation-parameters Data OPTIONAL
}

Action-Request-Next-Pblock ::= SEQUENCE
{
  invoke-id-and-priority Invoke-Id-And-Priority,
  block-number           Unsigned32
}

Action-Request-With-List ::= SEQUENCE
{
  invoke-id-and-priority       Invoke-Id-And-Priority,
  cosem-method-descriptor-list SEQUENCE OF Cosem-Method-Descriptor,
  method-invocation-parameters SEQUENCE OF Data -- null_data if method does not require parameters
}

Action-Request-With-First-Pblock ::= SEQUENCE
{
  invoke-id-and-priority  Invoke-Id-And-Priority,
  cosem-method-descriptor Cosem-Method-Descriptor,
  pblock                  DataBlock-SA
}

Action-Request-With-List-And-First-Pblock ::= SEQUENCE
{
  invoke-id-and-priority       Invoke-Id-And-Priority,
  cosem-method-descriptor-list SEQUENCE OF Cosem-Method-Descriptor,
  pblock                       DataBlock-SA
}

Action-Request-With-Pblock ::= SEQUENCE
{ 
  invoke-id-and-priority Invoke-Id-And-Priority,
  pBlock                 DataBlock-SA
} 

ACTION-Response ::= CHOICE
{ 
  action-response-normal      [1] IMPLICIT Action-Response-Normal,
  action-response-with-pblock [2] IMPLICIT Action-Response-With-Pblock,
  action-response-with-list   [3] IMPLICIT Action-Response-With-List,
  action-response-next-pblock [4] IMPLICIT Action-Response-Next-Pblock
}

Action-Response-Normal ::= SEQUENCE
{
  invoke-id-and-priority Invoke-Id-And-Priority,
  single-response        Action-Response-With-Optional-Data
}

Action-Response-With-Pblock ::= SEQUENCE
{ 
  invoke-id-and-priority Invoke-Id-And-Priority,
  pblock                 DataBlock-SA
} 

Action-Response-With-List ::= SEQUENCE
{ 
  invoke-id-and-priority Invoke-Id-And-Priority,
  list-of-responses      SEQUENCE OF Action-Response-With-Optional-Data
} 

Action-Response-Next-Pblock ::= SEQUENCE
{ 
  invoke-id-and-priority Invoke-Id-And-Priority,
  block-number           Unsigned32
} 

EVENT-NOTIFICATION-Request ::= SEQUENCE
{ 
  time                       Cosem-Date-Time OPTIONAL,
  cosem-attribute-descriptor Cosem-Attribute-Descriptor,
  attribute-value            Data
}
 
EXCEPTION-Response ::= SEQUENCE
{
  state_error   [0] IMPLICIT Enum,
  --{
  --  service_not_allowed [1],
  --  service_unknown     [2]
  --},
  service_error [1] IMPLICIT Enum
  --{
  --  operation_not_possible [1]
  --  service_not_supported  [2]
  --  other_reason           [3]
  --}
}

-------------------------------------------
-- APDUs using short name refencing

ReadRequest ::= SEQUENCE OF Variable-Access-Specification

ReadResponse ::= SEQUENCE OF CHOICE
{
  data              [0] Data,
  data-access-error [1] IMPLICIT Data-Access-Result
}

WriteRequest ::= SEQUENCE
{
  variable-access-specification SEQUENCE OF Variable-Access-Specification,
  list-of-data                  SEQUENCE OF Data
}

WriteResponse ::= SEQUENCE OF CHOICE
{
  success           [0] IMPLICIT NULL,
  data-access-error [1] IMPLICIT Data-Access-Result
}

UnconfirmedWriteRequest ::= SEQUENCE
{
  variable-access-specification SEQUENCE OF Variable-Access-Specification,
  list-of-data                  SEQUENCE OF Data
}

InformationReportRequest ::= SEQUENCE
{
  current-time                  GeneralizedTime OPTIONAL,
  variable-access-specification SEQUENCE OF Variable-Access-Specification,
  list-of-data                  SEQUENCE OF Data
}

END
